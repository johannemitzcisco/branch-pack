module branch {

  namespace "http://example.com/branch";
  prefix branch;

  import ietf-inet-types {
    prefix inet;
  }
  import tailf-common {
    prefix tailf;
  }
  import tailf-ncs {
    prefix ncs;
  }

  description
    "Bla bla...";

  revision 2017-08-02 {
    description
      "Initial revision.";
  }

  augment /ncs:devices/ncs:device {
    leaf uid {
      type string;
    }
  }
  
  typedef device-role {
    type enumeration {
      enum "router";
      enum "core";
      enum "access";
      enum "access-core";
      enum "distribution";
    }
  }

  typedef physical-interface-type {
    type enumeration {
      enum "GigabitEthernet";
      enum "TenGigabitEthernet";
    }
  }

  typedef logical-interface-type {
    type enumeration {
      enum "Vlan";
    }
  }

  typedef test-status {
    type enumeration {
      enum "UNKNOWN";
      enum "PASSED";
      enum "FAILED";
    }
  }

  grouping test-service {
    tailf:action test-service {
      tailf:info "Test connectivity to the SFO branch";
      tailf:actionpoint testservice-action;
      input {
      }
      output {
        leaf test-status {
          type string;
        }
      }
    }

    leaf service-status {
      type test-status;
      default "UNKNOWN";
    }
    list test {
      key "name";
      leaf name {
        type string;
      }
      leaf status {
        type test-status;
        default "UNKNOWN";
      }
      leaf device {
        type string;
      }
      leaf command {
        type string;
      }
      leaf-list match-criteria {
        tailf:info "Values that if found together on a line of output signifies success";
        type string;
      }
      leaf command-output {
        type string;
      }
    }
  }

  grouping device-general-config-grouping {
    list registration {
      key "policy-name";
      leaf policy-name {
        type leafref {
          path "/branch:branch-service/branch-policies/device/registration/name";
        }
      }
    }
    list loopback {
      key "policy-name interface-number";
      leaf policy-name {
        type leafref {
          path "/branch:branch-service/branch-policies/device/loopback/name";
        }
      }
      leaf interface-number {
        type uint8;
      }
      leaf ip-address {
        type inet:ipv4-address;
      }
    }
    list static-route {
      key "policy-name prefix mask";
      leaf policy-name {
        type leafref {
          path "/branch:branch-service/branch-policies/device/static-route/name";
        }
      }
      leaf prefix {
        type inet:ipv4-address;
      }
      leaf mask {
        type inet:ipv4-address;
      }
      leaf forwarding-address {
        type inet:ipv4-address;
      }
    }
  }

  grouping device-core-config-grouping {
  }

  grouping device-core-router-config-grouping {
    list ospf {
      key policy-name;
      leaf policy-name {
        type leafref {
          path "/branch:branch-service/branch-policies/device/ospf/name";
        }
      }
      leaf ip-address {
        type inet:ipv4-address;
      }
    }
  }

  grouping device-router-config-grouping {
    list netflow {
      key policy-name;
      leaf policy-name {
        type leafref {
          path "/branch:branch-service/branch-policies/device/netflow/name";
        }
      }
      leaf collector-ip-address {
        type inet:ipv4-address;
      }
    }
    list routing {
      key policy-name;
      leaf policy-name {
        type leafref {
          path "/branch:branch-service/branch-policies/device/routing/name";
        }
      }
      leaf as-number {
        type uint32;
      }
      list aggregate-address {
        key "ip-address ip-mask"; 
        leaf ip-address {
          type inet:ipv4-address;
        }
        leaf ip-mask {
          type inet:ipv4-address;
        }
      }
      container ebgp {
        leaf remote-as-number {
          type uint32;
        }
        leaf peer-ip-address {
          type inet:ipv4-address;
        }
        leaf carrier-name {
          type string;
        }
      }
    }
  }

  grouping device-access-config-grouping {
    list switchstack {
      key policy-name;
      leaf policy-name {
        type leafref {
          path "/branch:branch-service/branch-policies/device/switchstack/name";
        }
      }
      leaf switch-number {
        type uint32;
      }
    }
  }

  container branch-service {
    tailf:action load-topology-template {
      tailf:info "Load Topology Template";
      tailf:actionpoint loadservicetemplate-action;
      input {
        leaf branch-name {
          tailf:info "Name of the new branch";
          type string;
        }
        leaf topology-template {
          type leafref {
            path "/branch:branch-service/branch-policies/branch/topology-templates/name";
          }
        }
      }
      output {
      }
    }

    list branch {

      key name;
      leaf name {
        tailf:info "Unique branch id/name";
        type string;
      }

      uses ncs:service-data;
      ncs:servicepoint branch-servicepoint;

      uses test-service;

      container topology {
        list device {
          key topology-name;
          leaf topology-name {
            type string;
          }
          leaf hostname {
            type string;
          }
          leaf uid {
            type string;
          }
          container type {
            leaf role {
              type leafref {
                path "/branch:branch-service/branch-policies/device/role/name";
              }
            }
            leaf model {
              type leafref {
                path "/branch:branch-service/branch-policies/device/role[name=current()/../role]/model/name";
              }
            }
          }
          container policies {
            uses device-general-config-grouping;
            uses device-core-config-grouping {
              when "../type/role = 'core' or ../type/role = 'access-core'";
            }
            uses device-router-config-grouping {
              when "../type/role = 'router'";
            }
            uses device-core-router-config-grouping {
              when "../type/role = 'router' or ../type/role = 'core'";
            }
            uses device-access-config-grouping {
              when "../type/role = 'access' or ../type/role = 'access-core'";
            }
          }
        }
        list connection {
          key "name";
          leaf name {
            type string;
          }
          list side {
            min-elements 1;
            max-elements 2;
            key name;
            leaf name {
              type enumeration {
                enum "A";
                enum "B";
              }
            }
            leaf device {
              type leafref {
                path "../../../device/topology-name";
              }
            }
            list port {
              min-elements 1;
              max-elements 2;
              key "interface-type interface-name";
              leaf interface-type {
                type union {
                  type physical-interface-type;
                  type logical-interface-type;
                }
              }
              leaf interface-name {
                type string;
              }
              leaf ip-address {
                type inet:ipv4-address;
              }
              leaf ip-mask {
                type inet:ipv4-address;
              }
              leaf peer-interface {
                type string;
              }
            }
          }
          container type {
            choice type {
              container core-router {
                leaf policy-name {
                  type leafref {
                    path "/branch:branch-service/branch-policies/connection/core-router/name";
                  }
                }
              }
              container core-interlink {
                leaf policy-name {
                  type leafref {
                    path "/branch:branch-service/branch-policies/connection/core-interlink/name";
                  }
                }
              }
              container access-core {
                leaf policy-name {
                  type leafref {
                    path "/branch:branch-service/branch-policies/connection/access-core/name";
                  }
                }
              }
              container access-distribution {
                leaf policy-name {
                  type leafref {
                    path "/branch:branch-service/branch-policies/connection/access-distribution/name";
                  }
                }
              }
              container distribution-core {
                leaf policy-name {
                  type leafref {
                    path "/branch:branch-service/branch-policies/connection/distribution-core/name";
                  }
                }
              }
              container router-wan {
                leaf policy-name {
                  type leafref {
                    path "/branch:branch-service/branch-policies/connection/router-wan/name";
                  }
                }
              }
              container router-interlink {
                leaf policy-name {
                  type leafref {
                    path "/branch:branch-service/branch-policies/connection/router-interlink/name";
                  }
                }
              }
              container distribution-interlink {
                leaf policy-name {
                  type leafref {
                    path "/branch:branch-service/branch-policies/connection/distribution-interlink/name";
                  }
                }
              }
              container access {
                leaf policy-name {
                  type leafref {
                    path "/branch:branch-service/branch-policies/connection/access/name";
                  }
                }
                leaf access-type {
                  type enumeration {
                    enum "DATA";
                    enum "VOICE";
                    enum "WIRELESS";
                    enum "SECURITY";
                  } 
                }
                leaf helper-address {
                  type inet:ipv4-address;
                }
                leaf interface-type {
                  type physical-interface-type;
                }
                leaf interface-name {
                  type string;
                }
              }
            }
          }
        }
      }
    }

    container branch-policies {
      container branch {
        list topology-templates {
          key name;
          leaf name {
            type string;
          }
          leaf model-template-file {
            type string;
          }
        }
      }
      container connection {
        list core-router {
          key name;
          leaf name {
            type string;
          }
          container core {
            leaf template {
              type string;
            }
          }
          container router {
            leaf template {
              type string;
            }
          }
          container access-core {
            leaf template {
              type string;
            }
          }
        }
        list core-interlink {
          key name;
          leaf name {
            type string;
          }
          container core {
            leaf template {
              type string;
            }
          }
        }
        list distribution-interlink {
          key name;
          leaf name {
            type string;
          }
          container distribution {
            leaf template {
              type string;
            }
          }
        }
        list access-core {
          key name;
          leaf name {
            type string;
          }
          container access {
            leaf template {
              type string;
            }
          }
          container core {
            leaf template {
              type string;
            }
          }
        }
        list access-distribution {
          key name;
          leaf name {
            type string;
          }
          container access {
            leaf template {
              type string;
            }
          }
          container distribution {
            leaf template {
              type string;
            }
          }
        }
        list distribution-core {
          key name;
          leaf name {
            type string;
          }
          container distribution {
            leaf template {
              type string;
            }
          }
          container core {
            leaf template {
              type string;
            }
          }
        }
        list router-wan {
          key name;
          leaf name {
            type string;
          }
          container router {
            leaf template {
              type string;
            }
          }
          container core {
            leaf template {
              type string;
            }
          }
        }
        list router-interlink {
          key name;
          leaf name {
            type string;
          }
          container router {
            leaf template {
              type string;
            }
          }
        }
        list access {
          key name;
          leaf name {
            type string;
          }
          container access {
            leaf template {
              type string;
            }
          }
          container access-core {
            leaf template {
              type string;
            }
          }
        }
      }
      container device {
        list role {
          key name;
          leaf name {
            type device-role;
          }
          list model {
            key name;
            leaf name {
              type string;
            }
            leaf template {
              type string;
            }
          }
          container policies {
            leaf-list general {
              type leafref {
                path "../../../general/name";
              }
            }
            leaf-list vtp {
              max-elements 1;
              type leafref {
                path "../../../vtp/name";
              }
            }
            leaf-list ospf {
              max-elements 1;
              type leafref {
                path "../../../ospf/name";
              }
            }
            leaf-list netflow {
              max-elements 1;
              type leafref {
                path "../../../netflow/name";
              }
            }
            leaf-list ntp {
              max-elements 1;
              type leafref {
                path "../../../ntp/name";
              }
            }
          }
        }
        list general {
          key name;
          leaf name {
            type string;
          }
          leaf template {
            type string;
          }
        }
        list registration {
          key name;
          leaf name {
            type string;
          }
          leaf template {
            type string;
          }
        }
        list static-route {
          key name;
          leaf name {
            type string;
          }
          leaf template {
            type string;
          }
        }
        list loopback {
          key name;
          leaf name {
            type string;
          }
          leaf template {
            type string;
          }
        }
        list vtp {
          key name;
          leaf name {
            type string;
          }
          leaf domain-name {
            type string;
          }
          leaf template {
            type string;
          }
        }
        list ospf {
          key name;
          leaf name {
            type string;
          }
          leaf vlan {
            type string;
          }
          leaf template {
            type string;
          }
        }
        list netflow {
          key name;
          leaf name {
            type string;
          }
          leaf-list connection-type {
            type enumeration {
              enum "router-wan";
            }
          }
          leaf collector-ip-address {
            type inet:ipv4-address;
          }
          leaf template {
            type string;
          }
        }
        list ntp {
          key name;
          leaf name {
            type string;
          }
          leaf ip-address {
            type inet:ipv4-address;
          }
          leaf template {
            type string;
          }
        }
        list switchstack {
          key name;
          leaf name {
            type string;
          }
          leaf template {
            type string;
          }
        }
        list routing {
          key name;
          leaf name {
            type string;
          }
          leaf template {
            type string;
          }
        }
      }
    }
  }
}
